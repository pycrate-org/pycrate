-- ASN1START
-- **************************************************************
--
-- Constant definitions
--
-- **************************************************************

XnAP-Constants {
itu-t (0) identified-organization (4) etsi (0) mobileDomain (0)
ngran-Access (22) modules (3) xnap (2) version1 (1) xnap-Constants (4) }

DEFINITIONS AUTOMATIC TAGS ::=

BEGIN

IMPORTS
	ProcedureCode,
	ProtocolIE-ID
FROM XnAP-CommonDataTypes;

-- **************************************************************
--
-- Elementary Procedures
--
-- **************************************************************

id-handoverPreparation											ProcedureCode ::= 0
id-sNStatusTransfer												ProcedureCode ::= 1
id-handoverCancel												ProcedureCode ::= 2
id-retrieveUEContext											ProcedureCode ::= 3
id-rANPaging													ProcedureCode ::= 4
id-xnUAddressIndication											ProcedureCode ::= 5
id-uEContextRelease												ProcedureCode ::= 6
id-sNGRANnodeAdditionPreparation								ProcedureCode ::= 7
id-sNGRANnodeReconfigurationCompletion							ProcedureCode ::= 8
id-mNGRANnodeinitiatedSNGRANnodeModificationPreparation			ProcedureCode ::= 9
id-sNGRANnodeinitiatedSNGRANnodeModificationPreparation			ProcedureCode ::= 10
id-mNGRANnodeinitiatedSNGRANnodeRelease							ProcedureCode ::= 11
id-sNGRANnodeinitiatedSNGRANnodeRelease							ProcedureCode ::= 12
id-sNGRANnodeCounterCheck										ProcedureCode ::= 13
id-sNGRANnodeChange												ProcedureCode ::= 14
id-rRCTransfer													ProcedureCode ::= 15
id-xnRemoval													ProcedureCode ::= 16
id-xnSetup														ProcedureCode ::= 17
id-nGRANnodeConfigurationUpdate									ProcedureCode ::= 18
id-cellActivation												ProcedureCode ::= 19
id-reset														ProcedureCode ::= 20
id-errorIndication												ProcedureCode ::= 21
id-privateMessage												ProcedureCode ::= 22
id-notificationControl											ProcedureCode ::= 23
id-activityNotification											ProcedureCode ::= 24
id-e-UTRA-NR-CellResourceCoordination							ProcedureCode ::= 25
id-secondaryRATDataUsageReport									ProcedureCode ::= 26
id-deactivateTrace												ProcedureCode ::= 27
id-traceStart													ProcedureCode ::= 28
id-handoverSuccess												ProcedureCode ::= 29
id-conditionalHandoverCancel									ProcedureCode ::= 30
id-earlyStatusTransfer											ProcedureCode ::= 31
id-failureIndication											ProcedureCode ::= 32
id-handoverReport												ProcedureCode ::= 33
id-resourceStatusReportingInitiation							ProcedureCode ::= 34
id-resourceStatusReporting										ProcedureCode ::= 35
id-mobilitySettingsChange										ProcedureCode ::= 36
id-accessAndMobilityIndication									ProcedureCode ::= 37
id-cellTrafficTrace												ProcedureCode ::= 38
id-RANMulticastGroupPaging										ProcedureCode ::= 39
id-scgFailureInformationReport									ProcedureCode ::= 40
id-ProcedureCode41-NotToBeUsed									ProcedureCode ::= 41
id-scgFailureTransfer											ProcedureCode ::= 42
id-f1CTrafficTransfer											ProcedureCode ::= 43
id-iABTransportMigrationManagement								ProcedureCode ::= 44
id-iABTransportMigrationModification							ProcedureCode ::= 45
id-iABResourceCoordination										ProcedureCode ::= 46
id-retrieveUEContextConfirm										ProcedureCode ::= 47
id-cPCCancel													ProcedureCode ::= 48
id-partialUEContextTransfer										ProcedureCode ::= 49
id-rachIndication												ProcedureCode ::= 50
id-dataCollectionReportingInitiation							ProcedureCode ::= 51
id-dataCollectionReporting										ProcedureCode ::= 52



-- **************************************************************
--
-- Lists
--
-- **************************************************************

maxEARFCN									INTEGER ::= 262143
maxnoofAllowedAreas							INTEGER ::= 16
maxnoofAMFRegions							INTEGER ::= 16
maxnoofAoIs									INTEGER ::= 64
maxnoofBluetoothName						INTEGER ::= 4
maxnoofBPLMNs								INTEGER ::= 12
maxnoofCAGs									INTEGER ::= 12
maxnoofCAGsperPLMN							INTEGER ::= 256
maxnoofCellIDforMDT							INTEGER ::= 32
maxnoofCellsinAoI							INTEGER ::= 256
maxnoofCellsinUEHistoryInfo					INTEGER ::= 16
maxnoofCellsinNG-RANnode					INTEGER ::= 16384
maxnoofCellsinRNA							INTEGER ::= 32
maxnoofCellsUEMovingTrajectory				INTEGER ::= 16
maxnoofDRBs									INTEGER ::= 32
maxnoofEUTRABands							INTEGER ::= 16
maxnoofEUTRABPLMNs							INTEGER ::= 6
maxnoofEPLMNs								INTEGER ::= 15
maxnoofExtSliceItems						INTEGER ::= 65535
maxnoofEPLMNsplus1							INTEGER ::= 16
maxnoofForbiddenTACs						INTEGER ::= 4096
maxnoofFreqforMDT							INTEGER ::= 8
maxnoofMBSFNEUTRA							INTEGER ::= 8
maxnoofMDTPLMNs								INTEGER ::= 16
maxnoofMultiConnectivityMinusOne			INTEGER ::= 3
maxnoofNeighbours							INTEGER ::= 1024
maxnoofNeighPCIforMDT						INTEGER ::= 32
maxnoofNIDs									INTEGER ::= 12
maxnoofNRCellBands							INTEGER ::= 32
maxnoofPLMNs								INTEGER ::= 16
maxnoofPDUSessions							INTEGER ::= 256
maxnoofProtectedResourcePatterns			INTEGER ::= 16
maxnoofQoSFlows								INTEGER ::= 64
maxnoofQoSParaSets							INTEGER ::= 8
maxnoofRANAreaCodes							INTEGER ::= 32
maxnoofRANAreasinRNA						INTEGER ::= 16
maxnoofRANNodesinAoI						INTEGER ::= 64
maxnoofSCellGroups							INTEGER ::= 3
maxnoofSCellGroupsplus1						INTEGER ::= 4
maxnoofSensorName							INTEGER ::= 3
maxnoofSliceItems							INTEGER ::= 1024
maxnoofSNPNIDs								INTEGER ::= 12
maxnoofsupportedPLMNs						INTEGER ::= 12
maxnoofsupportedTACs						INTEGER ::= 256
maxnoofTAforMDT								INTEGER ::= 8
maxnoofTAI									INTEGER ::= 16
maxnoofTAIsinAoI							INTEGER ::= 16
maxnooftimeperiods							INTEGER ::= 2
maxnoofTNLAssociations						INTEGER ::= 32
maxnoofUEContexts							INTEGER ::= 8192
maxNRARFCN									INTEGER ::= 3279165
maxNrOfErrors								INTEGER ::= 256
maxnoofslots								INTEGER ::= 5120
maxnoofExtTLAs								INTEGER ::= 16
maxnoofGTPTLAs								INTEGER ::= 16
maxnoofCHOcells								INTEGER ::= 8
maxnoofPC5QoSFlows 							INTEGER ::= 2064
maxnoofSSBAreas								INTEGER ::= 64
maxnoofRAReports							INTEGER ::= 64
maxnoofNRSCSs								INTEGER ::= 5
maxnoofPhysicalResourceBlocks				INTEGER ::= 275
maxnoofAdditionalPDCPDuplicationTNL			INTEGER ::= 2
maxnoofRLCDuplicationstate					INTEGER ::= 3
maxnoofWLANName								INTEGER ::= 4
maxnoofNonAnchorCarrierFreqConfig			INTEGER ::= 15
maxnoofDataForwardingTunneltoE-UTRAN		INTEGER ::= 256
maxnoofMBSFSAs								INTEGER ::= 256
maxnoofUEIDIndicesforMBSPaging				INTEGER ::= 4096
maxnoofMBSQoSFlows							INTEGER ::= 64
maxnoofMRBs									INTEGER ::= 32
maxnoofCellsforMBS							INTEGER ::= 8192
maxnoofMBSServiceAreaInformation			INTEGER ::= 256
maxnoofTAIforMBS							INTEGER ::= 1024
maxnoofAssociatedMBSSessions				INTEGER ::= 32
maxnoofMBSSessions							INTEGER ::= 256
maxnoofSuccessfulHOReports					INTEGER ::= 64
maxnoofPSCellsPerSN							INTEGER ::= 8
maxnoofNR-UChannelIDs						INTEGER ::= 16
maxnoofCellsinCHO							INTEGER ::= 8
maxnoofCHOexecutioncond						INTEGER ::= 2
maxnoofServedCellsIAB						INTEGER ::= 512
maxnoofServingCells							INTEGER ::= 32
maxnoofBHInfo								INTEGER ::= 1024
maxnoofTrafficIndexEntries					INTEGER	::=	1024
maxnoofTLAsIAB								INTEGER	::=	1024
maxnoofBAPControlPDURLCCHs					INTEGER ::= 2
maxnoofIABSTCInfo							INTEGER ::= 45
maxnoofSymbols								INTEGER ::= 14
maxnoofDUFSlots								INTEGER ::= 320
maxnoofHSNASlots							INTEGER ::= 5120
maxnoofRBsetsPerCell						INTEGER ::= 8
maxnoofRBsetsPerCell1						INTEGER ::= 7
maxnoofChildIABNodes						INTEGER ::= 1024
maxnoofPSCellCandidates						INTEGER ::= 8
maxnoofTargetSNs							INTEGER ::= 8
maxnoofUEAppLayerMeas						INTEGER ::= 16
maxnoofSNSSAIforQMC							INTEGER ::= 16
maxnoofCellIDforQMC							INTEGER ::= 32
maxnoofPLMNforQMC							INTEGER ::= 16
maxnoofTAforQMC								INTEGER ::= 8
maxnoofMTCItems								INTEGER ::= 16
maxnoofCSIRSconfigurations					INTEGER ::= 96
maxnoofCSIRSneighbourCells					INTEGER ::= 16
maxnoofCSIRSneighbourCellsInMTC				INTEGER ::= 16
maxnoofNeighbour-NG-RAN-Nodes				INTEGER ::= 256
maxnoofSRBs									INTEGER ::= 5
maxnoofSMBR									INTEGER ::= 8
maxnoofNSAGs								INTEGER ::= 256
maxnoofTargetSNsMinusOne					INTEGER ::= 7
maxnoofThresholdsForExcessPacketDelay		INTEGER ::= 255
maxnoofESNPNs								INTEGER ::= 15
maxnoofSuccessfulPSCellChangeReports		INTEGER ::= 64
maxnoofUEsforRAReportIndications			INTEGER ::= 64
maxnoofPSCellsinCPAC						INTEGER ::= 8
maxnoofCPACexecutioncond					INTEGER ::= 2
maxnoofLBTFailureInformation				INTEGER ::= 64
maxnoofCellsTrajectoryPredict				INTEGER ::= 16
maxnoofCellsTrajectory						INTEGER	::=	16
maxFailedCellMeasObjects					INTEGER ::= 124
maxFailedMeasPerNode						INTEGER ::= 124
maxnoofUEReports							INTEGER ::= 16
maxnoofCandidateRelayUEs					INTEGER ::= 32
maxnoofCAGforMDT							INTEGER ::= 256
maxnoofMDTSNPNs								INTEGER ::= 16
maxnoofSecurityConfigurations				INTEGER ::= 8
maxnoofRSPPQoSFlows							INTEGER ::= 2048


-- **************************************************************
--
-- IEs
--
-- **************************************************************

id-ActivatedServedCells																				ProtocolIE-ID ::= 0
id-ActivationIDforCellActivation																	ProtocolIE-ID ::= 1
id-admittedSplitSRB																					ProtocolIE-ID ::= 2
id-admittedSplitSRBrelease																			ProtocolIE-ID ::= 3
id-AMF-Region-Information																			ProtocolIE-ID ::= 4
id-AssistanceDataForRANPaging																		ProtocolIE-ID ::= 5
id-BearersSubjectToCounterCheck																		ProtocolIE-ID ::= 6
id-Cause																							ProtocolIE-ID ::= 7
id-cellAssistanceInfo-NR																			ProtocolIE-ID ::= 8
id-ConfigurationUpdateInitiatingNodeChoice															ProtocolIE-ID ::= 9
id-CriticalityDiagnostics																			ProtocolIE-ID ::= 10
id-XnUAddressInfoperPDUSession-List																	ProtocolIE-ID ::= 11
id-DRBsSubjectToStatusTransfer-List																	ProtocolIE-ID ::= 12
id-ExpectedUEBehaviour																				ProtocolIE-ID ::= 13
id-GlobalNG-RAN-node-ID																				ProtocolIE-ID ::= 14
id-GUAMI																							ProtocolIE-ID ::= 15
id-indexToRatFrequSelectionPriority																	ProtocolIE-ID ::= 16
id-initiatingNodeType-ResourceCoordRequest															ProtocolIE-ID ::= 17
id-List-of-served-cells-E-UTRA																		ProtocolIE-ID ::= 18
id-List-of-served-cells-NR																			ProtocolIE-ID ::= 19
id-LocationReportingInformation																		ProtocolIE-ID ::= 20
id-MAC-I																							ProtocolIE-ID ::= 21
id-MaskedIMEISV																						ProtocolIE-ID ::= 22
id-M-NG-RANnodeUEXnAPID																				ProtocolIE-ID ::= 23
id-MN-to-SN-Container																				ProtocolIE-ID ::= 24
id-MobilityRestrictionList																			ProtocolIE-ID ::= 25
id-new-NG-RAN-Cell-Identity																			ProtocolIE-ID ::= 26
id-newNG-RANnodeUEXnAPID																			ProtocolIE-ID ::= 27
id-UEReportRRCTransfer																				ProtocolIE-ID ::= 28
id-oldNG-RANnodeUEXnAPID																			ProtocolIE-ID ::= 29
id-OldtoNewNG-RANnodeResumeContainer																ProtocolIE-ID ::= 30
id-PagingDRX																						ProtocolIE-ID ::= 31
id-PCellID																							ProtocolIE-ID ::= 32
id-PDCPChangeIndication																				ProtocolIE-ID ::= 33
id-PDUSessionAdmittedAddedAddReqAck																	ProtocolIE-ID ::= 34
id-PDUSessionAdmittedModSNModConfirm																ProtocolIE-ID ::= 35
id-PDUSessionAdmitted-SNModResponse																	ProtocolIE-ID ::= 36
id-PDUSessionNotAdmittedAddReqAck																	ProtocolIE-ID ::= 37
id-PDUSessionNotAdmitted-SNModResponse																ProtocolIE-ID ::= 38
id-PDUSessionReleasedList-RelConf																	ProtocolIE-ID ::= 39
id-PDUSessionReleasedSNModConfirm																	ProtocolIE-ID ::= 40
id-PDUSessionResourcesActivityNotifyList															ProtocolIE-ID ::= 41
id-PDUSessionResourcesAdmitted-List																	ProtocolIE-ID ::= 42
id-PDUSessionResourcesNotAdmitted-List																ProtocolIE-ID ::= 43
id-PDUSessionResourcesNotifyList																	ProtocolIE-ID ::= 44
id-PDUSession-SNChangeConfirm-List																	ProtocolIE-ID ::= 45
id-PDUSession-SNChangeRequired-List																	ProtocolIE-ID ::= 46
id-PDUSessionToBeAddedAddReq																		ProtocolIE-ID ::= 47
id-PDUSessionToBeModifiedSNModRequired																ProtocolIE-ID ::= 48
id-PDUSessionToBeReleasedList-RelRqd																ProtocolIE-ID ::= 49
id-PDUSessionToBeReleased-RelReq																	ProtocolIE-ID ::= 50
id-PDUSessionToBeReleasedSNModRequired																ProtocolIE-ID ::= 51
id-RANPagingArea																					ProtocolIE-ID ::= 52
id-PagingPriority																					ProtocolIE-ID ::= 53
id-requestedSplitSRB																				ProtocolIE-ID ::= 54
id-requestedSplitSRBrelease																			ProtocolIE-ID ::= 55
id-ResetRequestTypeInfo																				ProtocolIE-ID ::= 56
id-ResetResponseTypeInfo																			ProtocolIE-ID ::= 57
id-RespondingNodeTypeConfigUpdateAck																ProtocolIE-ID ::= 58
id-respondingNodeType-ResourceCoordResponse															ProtocolIE-ID ::= 59
id-ResponseInfo-ReconfCompl																			ProtocolIE-ID ::= 60
id-RRCConfigIndication																				ProtocolIE-ID ::= 61
id-RRCResumeCause																					ProtocolIE-ID ::= 62
id-SCGConfigurationQuery																			ProtocolIE-ID ::= 63
id-selectedPLMN																						ProtocolIE-ID ::= 64
id-ServedCellsToActivate																			ProtocolIE-ID ::= 65
id-servedCellsToUpdate-E-UTRA																		ProtocolIE-ID ::= 66
id-ServedCellsToUpdateInitiatingNodeChoice															ProtocolIE-ID ::= 67
id-servedCellsToUpdate-NR																			ProtocolIE-ID ::= 68
id-s-ng-RANnode-SecurityKey																			ProtocolIE-ID ::= 69
id-S-NG-RANnodeUE-AMBR																				ProtocolIE-ID ::= 70
id-S-NG-RANnodeUEXnAPID																				ProtocolIE-ID ::= 71
id-SN-to-MN-Container																				ProtocolIE-ID ::= 72
id-sourceNG-RANnodeUEXnAPID																			ProtocolIE-ID ::= 73
id-SplitSRB-RRCTransfer																				ProtocolIE-ID ::= 74
id-TAISupport-list																					ProtocolIE-ID ::= 75
id-TimeToWait																						ProtocolIE-ID ::= 76
id-Target2SourceNG-RANnodeTranspContainer															ProtocolIE-ID ::= 77
id-targetCellGlobalID																				ProtocolIE-ID ::= 78
id-targetNG-RANnodeUEXnAPID																			ProtocolIE-ID ::= 79
id-target-S-NG-RANnodeID																			ProtocolIE-ID ::= 80
id-TraceActivation																					ProtocolIE-ID ::= 81
id-UEContextID																						ProtocolIE-ID ::= 82
id-UEContextInfoHORequest																			ProtocolIE-ID ::= 83
id-UEContextInfoRetrUECtxtResp																		ProtocolIE-ID ::= 84
id-UEContextInfo-SNModRequest																		ProtocolIE-ID ::= 85
id-UEContextKeptIndicator																			ProtocolIE-ID ::= 86
id-UEContextRefAtSN-HORequest																		ProtocolIE-ID ::= 87
id-UEHistoryInformation																				ProtocolIE-ID ::= 88
id-UEIdentityIndexValue																				ProtocolIE-ID ::= 89
id-UERANPagingIdentity																				ProtocolIE-ID ::= 90
id-UESecurityCapabilities																			ProtocolIE-ID ::= 91
id-UserPlaneTrafficActivityReport																	ProtocolIE-ID ::= 92
id-XnRemovalThreshold																				ProtocolIE-ID ::= 93
id-DesiredActNotificationLevel																		ProtocolIE-ID ::= 94
id-AvailableDRBIDs																					ProtocolIE-ID ::= 95
id-AdditionalDRBIDs																					ProtocolIE-ID ::= 96
id-SpareDRBIDs 																						ProtocolIE-ID ::= 97
id-RequiredNumberOfDRBIDs																			ProtocolIE-ID ::= 98
id-TNLA-To-Add-List																					ProtocolIE-ID ::= 99
id-TNLA-To-Update-List																				ProtocolIE-ID ::= 100
id-TNLA-To-Remove-List																				ProtocolIE-ID ::= 101
id-TNLA-Setup-List																					ProtocolIE-ID ::= 102
id-TNLA-Failed-To-Setup-List																		ProtocolIE-ID ::= 103
id-PDUSessionToBeReleased-RelReqAck																	ProtocolIE-ID ::= 104
id-S-NG-RANnodeMaxIPDataRate-UL																		ProtocolIE-ID ::= 105
id-PDUSessionResourceSecondaryRATUsageList															ProtocolIE-ID ::= 107
id-Additional-UL-NG-U-TNLatUPF-List																	ProtocolIE-ID ::= 108
id-SecondarydataForwardingInfoFromTarget-List														ProtocolIE-ID ::= 109
id-LocationInformationSNReporting																	ProtocolIE-ID ::= 110
id-LocationInformationSN																			ProtocolIE-ID ::= 111
id-LastE-UTRANPLMNIdentity																			ProtocolIE-ID ::= 112
id-S-NG-RANnodeMaxIPDataRate-DL																		ProtocolIE-ID ::= 113
id-MaxIPrate-DL																						ProtocolIE-ID ::= 114
id-SecurityResult																					ProtocolIE-ID ::= 115
id-S-NSSAI																							ProtocolIE-ID ::= 116
id-MR-DC-ResourceCoordinationInfo																	ProtocolIE-ID ::= 117
id-AMF-Region-Information-To-Add																	ProtocolIE-ID ::= 118
id-AMF-Region-Information-To-Delete																	ProtocolIE-ID ::= 119
id-OldQoSFlowMap-ULendmarkerexpected																ProtocolIE-ID ::= 120
id-RANPagingFailure																					ProtocolIE-ID ::= 121
id-UERadioCapabilityForPaging																		ProtocolIE-ID ::= 122
id-PDUSessionDataForwarding-SNModResponse															ProtocolIE-ID ::= 123
id-DRBsNotAdmittedSetupModifyList																	ProtocolIE-ID ::= 124
id-Secondary-MN-Xn-U-TNLInfoatM																		ProtocolIE-ID ::= 125
id-NE-DC-TDM-Pattern																				ProtocolIE-ID ::= 126
id-PDUSessionCommonNetworkInstance																	ProtocolIE-ID ::= 127
id-BPLMN-ID-Info-EUTRA																				ProtocolIE-ID ::= 128
id-BPLMN-ID-Info-NR																					ProtocolIE-ID ::= 129
id-InterfaceInstanceIndication																		ProtocolIE-ID ::= 130
id-S-NG-RANnode-Addition-Trigger-Ind																ProtocolIE-ID ::= 131
id-DefaultDRB-Allowed																				ProtocolIE-ID ::= 132
id-DRB-IDs-takenintouse																				ProtocolIE-ID ::= 133
id-SplitSessionIndicator																			ProtocolIE-ID ::= 134
id-CNTypeRestrictionsForEquivalent																	ProtocolIE-ID ::= 135
id-CNTypeRestrictionsForServing																		ProtocolIE-ID ::= 136
id-DRBs-transferred-to-MN																			ProtocolIE-ID ::= 137
id-ULForwardingProposal																				ProtocolIE-ID ::= 138
id-EndpointIPAddressAndPort																			ProtocolIE-ID ::= 139
id-IntendedTDD-DL-ULConfiguration-NR																ProtocolIE-ID ::= 140
id-TNLConfigurationInfo																				ProtocolIE-ID ::= 141
id-PartialListIndicator-NR																			ProtocolIE-ID ::= 142
id-MessageOversizeNotification																		ProtocolIE-ID ::= 143
id-CellAndCapacityAssistanceInfo-NR																	ProtocolIE-ID ::= 144
id-NG-RANTraceID																					ProtocolIE-ID ::= 145
id-NonGBRResources-Offered																			ProtocolIE-ID ::= 146
id-FastMCGRecoveryRRCTransfer-SN-to-MN																ProtocolIE-ID ::= 147
id-RequestedFastMCGRecoveryViaSRB3																	ProtocolIE-ID ::= 148
id-AvailableFastMCGRecoveryViaSRB3																	ProtocolIE-ID ::= 149
id-RequestedFastMCGRecoveryViaSRB3Release															ProtocolIE-ID ::= 150
id-ReleaseFastMCGRecoveryViaSRB3																	ProtocolIE-ID ::= 151
id-FastMCGRecoveryRRCTransfer-MN-to-SN																ProtocolIE-ID ::= 152
id-ExtendedRATRestrictionInformation																ProtocolIE-ID ::= 153
id-QoSMonitoringRequest																				ProtocolIE-ID ::= 154
id-FiveGCMobilityRestrictionListContainer															ProtocolIE-ID ::= 155
id-PartialListIndicator-EUTRA																		ProtocolIE-ID ::= 156
id-CellAndCapacityAssistanceInfo-EUTRA																ProtocolIE-ID ::= 157
id-CHOinformation-Req																				ProtocolIE-ID ::= 158
id-CHOinformation-Ack																				ProtocolIE-ID ::= 159
id-targetCellsToCancel																				ProtocolIE-ID ::= 160
id-requestedTargetCellGlobalID																		ProtocolIE-ID ::= 161
id-procedureStage																					ProtocolIE-ID ::= 162
id-DAPSRequestInfo																					ProtocolIE-ID ::= 163
id-DAPSResponseInfo-List																			ProtocolIE-ID ::= 164
id-CHO-MRDC-Indicator																				ProtocolIE-ID ::= 165
id-OffsetOfNbiotChannelNumberToDL-EARFCN															ProtocolIE-ID ::= 166
id-OffsetOfNbiotChannelNumberToUL-EARFCN															ProtocolIE-ID ::= 167
id-NBIoT-UL-DL-AlignmentOffset																		ProtocolIE-ID ::= 168
id-LTEV2XServicesAuthorized																			ProtocolIE-ID ::= 169
id-NRV2XServicesAuthorized																			ProtocolIE-ID ::= 170
id-LTEUESidelinkAggregateMaximumBitRate																ProtocolIE-ID ::= 171
id-NRUESidelinkAggregateMaximumBitRate																ProtocolIE-ID ::= 172
id-PC5QoSParameters																					ProtocolIE-ID ::= 173
id-AlternativeQoSParaSetList																		ProtocolIE-ID ::= 174
id-CurrentQoSParaSetIndex																			ProtocolIE-ID ::= 175
id-MobilityInformation																				ProtocolIE-ID ::= 176
id-InitiatingCondition-FailureIndication															ProtocolIE-ID ::= 177
id-UEHistoryInformationFromTheUE																	ProtocolIE-ID ::= 178
id-HandoverReportType																				ProtocolIE-ID ::= 179
id-HandoverCause																					ProtocolIE-ID ::= 180
id-SourceCellCGI																					ProtocolIE-ID ::= 181
id-TargetCellCGI																					ProtocolIE-ID ::= 182
id-ReEstablishmentCellCGI																			ProtocolIE-ID ::= 183
id-TargetCellinEUTRAN																				ProtocolIE-ID ::= 184
id-SourceCellCRNTI																					ProtocolIE-ID ::= 185
id-UERLFReportContainer																				ProtocolIE-ID ::= 186
id-NGRAN-Node1-Measurement-ID																		ProtocolIE-ID ::= 187
id-NGRAN-Node2-Measurement-ID																		ProtocolIE-ID ::= 188
id-RegistrationRequest																				ProtocolIE-ID ::= 189
id-ReportCharacteristics																				ProtocolIE-ID ::= 190
id-CellToReport																								ProtocolIE-ID ::= 191
id-ReportingPeriodicity																					ProtocolIE-ID ::= 192
id-CellMeasurementResult																				ProtocolIE-ID ::= 193
id-NG-RANnode1CellID																						ProtocolIE-ID ::= 194
id-NG-RANnode2CellID																				ProtocolIE-ID ::= 195
id-NG-RANnode1MobilityParameters																	ProtocolIE-ID ::= 196
id-NG-RANnode2ProposedMobilityParameters															ProtocolIE-ID ::= 197
id-MobilityParametersModificationRange																ProtocolIE-ID ::= 198
id-TDDULDLConfigurationCommonNR																		ProtocolIE-ID ::= 199
id-CarrierList																						ProtocolIE-ID ::= 200
id-ULCarrierList																					ProtocolIE-ID ::= 201
id-FrequencyShift7p5khz																				ProtocolIE-ID ::= 202
id-SSB-PositionsInBurst																				ProtocolIE-ID ::= 203
id-NRCellPRACHConfig																				ProtocolIE-ID ::= 204
id-RAReport																							ProtocolIE-ID ::= 205
id-IABNodeIndication																				ProtocolIE-ID ::= 206
id-Redundant-UL-NG-U-TNLatUPF																		ProtocolIE-ID ::= 207
id-CNPacketDelayBudgetDownlink																		ProtocolIE-ID ::= 208
id-CNPacketDelayBudgetUplink																		ProtocolIE-ID ::= 209
id-Additional-Redundant-UL-NG-U-TNLatUPF-List														ProtocolIE-ID ::= 210
id-RedundantCommonNetworkInstance																	ProtocolIE-ID ::= 211
id-TSCTrafficCharacteristics																		ProtocolIE-ID ::= 212
id-RedundantQoSFlowIndicator																		ProtocolIE-ID ::= 213
id-Redundant-DL-NG-U-TNLatNG-RAN																	ProtocolIE-ID ::= 214
id-ExtendedPacketDelayBudget																		ProtocolIE-ID ::= 215
id-Additional-PDCP-Duplication-TNL-List																ProtocolIE-ID ::= 216
id-RedundantPDUSessionInformation																	ProtocolIE-ID ::= 217
id-UsedRSNInformation																				ProtocolIE-ID ::= 218
id-RLCDuplicationInformation																		ProtocolIE-ID ::= 219
id-NPN-Broadcast-Information																		ProtocolIE-ID ::= 220
id-NPNPagingAssistanceInformation																	ProtocolIE-ID ::= 221
id-NPNMobilityInformation																			ProtocolIE-ID ::= 222
id-NPN-Support																						ProtocolIE-ID ::= 223
id-MDT-Configuration																				ProtocolIE-ID ::= 224
id-MDTPLMNList																						ProtocolIE-ID ::= 225
id-TraceCollectionEntityURI																			ProtocolIE-ID ::= 226
id-UERadioCapabilityID																				ProtocolIE-ID ::= 227
id-CSI-RSTransmissionIndication																		ProtocolIE-ID ::= 228
id-SNTriggered																						ProtocolIE-ID ::= 229
id-DLCarrierList																					ProtocolIE-ID ::= 230
id-ExtendedTAISliceSupportList																		ProtocolIE-ID ::= 231
id-cellAssistanceInfo-EUTRA																			ProtocolIE-ID ::= 232
id-ConfiguredTACIndication																			ProtocolIE-ID ::= 233
id-secondary-SN-UL-PDCP-UP-TNLInfo																	ProtocolIE-ID ::= 234
id-pdcpDuplicationConfiguration																		ProtocolIE-ID ::= 235
id-duplicationActivation																			ProtocolIE-ID ::= 236
id-NPRACHConfiguration																				ProtocolIE-ID ::= 237
id-QosMonitoringReportingFrequency																	ProtocolIE-ID ::= 238
id-QoSFlowsMappedtoDRB-SetupResponse-MNterminated													ProtocolIE-ID ::= 239
id-DL-scheduling-PDCCH-CCE-usage																	ProtocolIE-ID ::= 240
id-UL-scheduling-PDCCH-CCE-usage																	ProtocolIE-ID ::= 241
id-SFN-Offset																						ProtocolIE-ID ::= 242
id-QoSMonitoringDisabled																			ProtocolIE-ID ::= 243
id-ExtendedUEIdentityIndexValue																		ProtocolIE-ID ::= 244
id-EUTRAPagingeDRXInformation																		ProtocolIE-ID ::= 245
id-CHO-MRDC-EarlyDataForwarding																		ProtocolIE-ID ::= 246
id-SCGIndicator																						ProtocolIE-ID ::= 247
id-UESpecificDRX																					ProtocolIE-ID ::= 248
id-PDUSessionExpectedUEActivityBehaviour															ProtocolIE-ID ::= 249
id-QoS-Mapping-Information																			ProtocolIE-ID ::= 250
id-AdditionLocationInformation																		ProtocolIE-ID ::= 251
id-dataForwardingInfoFromTargetE-UTRANnode															ProtocolIE-ID ::= 252
id-DirectForwardingPathAvailability																	ProtocolIE-ID ::= 253
id-SourceNG-RAN-node-ID																				ProtocolIE-ID ::= 254
id-SourceDLForwardingIPAddress																		ProtocolIE-ID ::= 255
id-SourceNodeDLForwardingIPAddress																	ProtocolIE-ID ::= 256
id-ExtendedReportIntervalMDT																		ProtocolIE-ID ::= 257
id-SecurityIndication																				ProtocolIE-ID ::= 258
id-RRCConnReestab-Indicator																			ProtocolIE-ID ::= 259
id-TargetNodeID																						ProtocolIE-ID ::= 260
id-ManagementBasedMDTPLMNList																		ProtocolIE-ID ::= 261
id-PrivacyIndicator																					ProtocolIE-ID ::= 262
id-TraceCollectionEntityIPAddress																	ProtocolIE-ID ::= 263
id-M4ReportAmount																					ProtocolIE-ID ::= 264
id-M5ReportAmount																					ProtocolIE-ID ::= 265
id-M6ReportAmount																					ProtocolIE-ID ::= 266
id-M7ReportAmount																					ProtocolIE-ID ::= 267
id-BeamMeasurementIndicationM1																		ProtocolIE-ID ::= 268
id-MBS-Session-ID																					ProtocolIE-ID ::= 269
id-UEIdentityIndexList-MBSGroupPaging																	ProtocolIE-ID ::= 270
id-MulticastRANPagingArea																			ProtocolIE-ID ::= 271
id-Supported-MBS-FSA-ID-List																		ProtocolIE-ID ::= 272
id-MBS-SessionInformation-List																		ProtocolIE-ID ::= 273
id-MBS-SessionInformationResponse-List																ProtocolIE-ID ::= 274
id-MBS-SessionAssociatedInformation																	ProtocolIE-ID ::= 275
id-SuccessfulHOReportInformation																	ProtocolIE-ID ::= 276
id-SliceRadioResourceStatus-List																	ProtocolIE-ID ::= 277
id-CompositeAvailableCapacitySupplementaryUplink													ProtocolIE-ID ::= 278
id-SCGUEHistoryInformation																			ProtocolIE-ID ::= 279
id-SSBOffsets-List																					ProtocolIE-ID ::= 280
id-NG-RANnode2SSBOffsetModificationRange															ProtocolIE-ID ::= 281
id-Coverage-Modification-List																		ProtocolIE-ID ::= 282
id-NR-U-Channel-List																				ProtocolIE-ID ::= 283
id-SourcePSCellCGI																					ProtocolIE-ID ::= 284
id-FailedPSCellCGI																					ProtocolIE-ID ::= 285
id-SCGFailureReportContainer																		ProtocolIE-ID ::= 286
id-SNMobilityInformation																			ProtocolIE-ID ::= 287
id-SourcePSCellID																					ProtocolIE-ID ::= 288
id-SuitablePSCellCGI																				ProtocolIE-ID ::= 289
id-PSCellChangeHistory																				ProtocolIE-ID ::= 290
id-CHOConfiguration																					ProtocolIE-ID ::= 291
id-NR-U-ChannelInfo-List																			ProtocolIE-ID ::= 292
id-PSCellHistoryInformationRetrieve																	ProtocolIE-ID ::= 293
id-NG-RANnode2SSBOffsetsModificationRange															ProtocolIE-ID ::= 294
id-MIMOPRBusageInformation																			ProtocolIE-ID ::= 295
id-F1CTrafficContainer																				ProtocolIE-ID ::= 296
id-IAB-MT-Cell-List																					ProtocolIE-ID ::= 297
id-NoPDUSessionIndication																			ProtocolIE-ID ::= 298
id-IAB-TNL-Address-Request																			ProtocolIE-ID ::= 299
id-IAB-TNL-Address-Response																			ProtocolIE-ID ::= 300
id-TrafficToBeAddedList																				ProtocolIE-ID ::= 301
id-TrafficToBeModifiedList																			ProtocolIE-ID ::= 302
id-TrafficToBeReleaseInformation																	ProtocolIE-ID ::= 303
id-TrafficAddedList																					ProtocolIE-ID ::= 304
id-TrafficModifiedList																				ProtocolIE-ID ::= 305
id-TrafficNotAddedList																				ProtocolIE-ID ::= 306
id-TrafficNotModifiedList																			ProtocolIE-ID ::= 307
id-TrafficRequiredToBeModifiedList																	ProtocolIE-ID ::= 308
id-TrafficRequiredModifiedList																		ProtocolIE-ID ::= 309
id-TrafficReleasedList																				ProtocolIE-ID ::= 310
id-IABTNLAddressToBeAdded																			ProtocolIE-ID ::= 311
id-IABTNLAddressToBeReleasedList																	ProtocolIE-ID ::= 312
id-nonF1-Terminating-IAB-DonorUEXnAPID																ProtocolIE-ID ::= 313
id-F1-Terminating-IAB-DonorUEXnAPID																	ProtocolIE-ID ::= 314
id-BoundaryNodeCellsList																			ProtocolIE-ID ::= 315
id-ParentNodeCellsList																				ProtocolIE-ID ::= 316
id-tdd-GNB-DU-Cell-Resource-Configuration															ProtocolIE-ID ::= 317
id-UL-GNB-DU-Cell-Resource-Configuration															ProtocolIE-ID ::= 318
id-DL-GNB-DU-Cell-Resource-Configuration															ProtocolIE-ID ::= 319
id-permutation																						ProtocolIE-ID ::= 320
id-IABTNLAddressException																			ProtocolIE-ID ::= 321
id-CHOinformation-AddReq																			ProtocolIE-ID ::= 322
id-CHOinformation-ModReq																			ProtocolIE-ID ::= 323
id-SurvivalTime																						ProtocolIE-ID ::= 324
id-TimeSynchronizationAssistanceInformation															ProtocolIE-ID ::= 325
id-SCGActivationRequest																				ProtocolIE-ID ::= 326
id-SCGActivationStatus																				ProtocolIE-ID ::= 327
id-CPAInformationRequest																			ProtocolIE-ID ::= 328
id-CPAInformationAck																				ProtocolIE-ID ::= 329
id-CPCInformationRequired																			ProtocolIE-ID ::= 330
id-CPCInformationConfirm																			ProtocolIE-ID ::= 331
id-CPAInformationModReq																				ProtocolIE-ID ::= 332
id-CPAInformationModReqAck																			ProtocolIE-ID ::= 333
id-CPC-DataForwarding-Indicator																		ProtocolIE-ID ::= 334
id-CPCInformationUpdate																				ProtocolIE-ID ::= 335
id-CPACInformationModRequired																		ProtocolIE-ID ::= 336
id-QMCConfigInfo																					ProtocolIE-ID ::= 337
id-ProtocolIE-ID338-NotToBeUsed																		ProtocolIE-ID ::= 338
id-Additional-Measurement-Timing-Configuration-List													ProtocolIE-ID ::= 339
id-PDUSession-PairID																				ProtocolIE-ID ::= 340
id-Local-NG-RAN-Node-Identifier																		ProtocolIE-ID ::= 341
id-Neighbour-NG-RAN-Node-List																		ProtocolIE-ID ::= 342
id-Local-NG-RAN-Node-Identifier-Removal																ProtocolIE-ID ::= 343
id-FiveGProSeAuthorized																				ProtocolIE-ID ::= 344
id-FiveGProSePC5QoSParameters																		ProtocolIE-ID ::= 345
id-FiveGProSeUEPC5AggregateMaximumBitRate															ProtocolIE-ID ::= 346
id-ServedCellSpecificInfoReq-NR																		ProtocolIE-ID ::= 347
id-NRPagingeDRXInformation																			ProtocolIE-ID ::= 348
id-NRPagingeDRXInformationforRRCINACTIVE															ProtocolIE-ID ::= 349
id-Redcap-Bcast-Information																			ProtocolIE-ID ::= 350
id-SDTSupportRequest																				ProtocolIE-ID ::= 351
id-SDT-SRB-between-NewNode-OldNode																	ProtocolIE-ID ::= 352
id-SDT-Termination-Request																			ProtocolIE-ID ::= 353
id-SDTPartialUEContextInfo																			ProtocolIE-ID ::= 354
id-SDTDataForwardingDRBList																			ProtocolIE-ID ::= 355
id-PagingCause																						ProtocolIE-ID ::= 356
id-PEIPSassistanceInformation																		ProtocolIE-ID ::= 357
id-UESliceMaximumBitRateList																		ProtocolIE-ID ::= 358
id-S-NG-RANnodeUE-Slice-MBR																			ProtocolIE-ID ::= 359
id-PositioningInformation																			ProtocolIE-ID ::= 360
id-UEAssistantIdentifier																			ProtocolIE-ID ::= 361
id-ManagementBasedMDTPLMNModificationList															ProtocolIE-ID ::= 362
id-F1-terminatingIAB-donorIndicator																	ProtocolIE-ID ::= 363
id-TAINSAGSupportList																				ProtocolIE-ID ::= 364
id-SCGreconfigNotification																			ProtocolIE-ID ::= 365
id-earlyMeasurement																					ProtocolIE-ID ::= 366
id-BeamMeasurementsReportConfiguration																ProtocolIE-ID ::= 367
id-CoverageModificationCause																		ProtocolIE-ID ::= 368
id-AdditionalListofPDUSessionResourceChangeConfirmInfo-SNterminated									ProtocolIE-ID ::= 369
id-UERLFReportContainerLTEExtension																ProtocolIE-ID ::= 370
id-ExcessPacketDelayThresholdConfiguration															ProtocolIE-ID ::= 371
id-HashedUEIdentityIndexValue																		ProtocolIE-ID ::= 372
id-QosFlowMappingIndication																			ProtocolIE-ID ::= 373
id-Full-and-Short-I-RNTI-Profile-List																ProtocolIE-ID ::= 374
id-MBS-DataForwarding-Indicator																		ProtocolIE-ID ::= 375
id-IABAuthorizationStatus																			ProtocolIE-ID ::= 376
id-EquivalentSNPNs																					ProtocolIE-ID ::= 377
id-SelectedNID																						ProtocolIE-ID ::= 378
id-MT-SDT-Information																				ProtocolIE-ID ::= 379
id-PosPartialUEContextInfo																			ProtocolIE-ID ::= 380
id-SRSConfiguration																					ProtocolIE-ID ::= 381
id-CHOTimeBasedInformation																			ProtocolIE-ID ::= 382
id-ChannelOccupancyTimePercentageUL																	ProtocolIE-ID ::= 383
id-EnergyDetectionThresholdUL																		ProtocolIE-ID ::= 384
id-SuccessfulPSCellChangeReportInformation															ProtocolIE-ID ::= 385
id-PSCellListContainer																				ProtocolIE-ID ::= 386
id-RadioResourceStatusNR-U																			ProtocolIE-ID ::= 387
id-CPACConfiguration																				ProtocolIE-ID ::= 388
id-RaReportIndicationList																			ProtocolIE-ID ::= 389
id-SPRAvailability																					ProtocolIE-ID ::= 390
id-DLLBTFailureInformationRequest																	ProtocolIE-ID ::= 391
id-DLLBTFailureInformationList																		ProtocolIE-ID ::= 392
id-TargetCellCRNTI																					ProtocolIE-ID ::= 393
id-TimeSinceFailure																					ProtocolIE-ID ::= 394
id-AerialUESubscriptionInformation																	ProtocolIE-ID ::= 395
id-LTEA2XServicesAuthorized																			ProtocolIE-ID ::= 396
id-NRA2XServicesAuthorized																			ProtocolIE-ID ::= 397
id-LTEA2XUEPC5AggregateMaximumBitRate																ProtocolIE-ID ::= 398
id-NRA2XUEPC5AggregateMaximumBitRate																ProtocolIE-ID ::= 399
id-A2XPC5QoSParameters																				ProtocolIE-ID ::= 400
id-CellBasedUETrajectoryPrediction																	ProtocolIE-ID ::= 401
id-DataCollectionID																					ProtocolIE-ID ::= 402
id-RequestedPredictionTime																			ProtocolIE-ID ::= 403
id-NodeMeasurementInitiationResult-List																ProtocolIE-ID ::= 404
id-CellMeasurementInitiationResult-List																ProtocolIE-ID ::= 405
id-UEAssociatedInfoResult-List																		ProtocolIE-ID ::= 406
id-ProtocolIE-ID-407-not-to-be-used																	ProtocolIE-ID ::= 407
id-UETrajectoryCollectionConfiguration																ProtocolIE-ID ::= 408
id-UEPerformanceCollectionConfiguration																ProtocolIE-ID ::= 409
id-CellMeasurementResultForDataCollection-List															ProtocolIE-ID ::= 410
id-CellToReportForDataCollection-List																ProtocolIE-ID ::= 411
id-FiveGProSeLayer2Multipath																		ProtocolIE-ID ::= 412
id-FiveGProSeLayer2UEtoUERelay																		ProtocolIE-ID ::= 413
id-FiveGProSeLayer2UEtoUERemote																		ProtocolIE-ID ::= 414
id-CandidateRelayUEInfoList																			ProtocolIE-ID ::= 415
id-NRCellsAndSSBsList																				ProtocolIE-ID ::= 416
id-ActivatedNRCellsAndSSBsList																		ProtocolIE-ID ::= 417
id-ClockQualityReportingControlInfo																	ProtocolIE-ID ::= 418
id-CapabilityForBATAdaptation																		ProtocolIE-ID ::= 419
id-PNI-NPN-AreaScopeofMDT																			ProtocolIE-ID ::= 420
id-PNI-NPNBasedMDT																					ProtocolIE-ID ::= 421
id-SNPN-CellBasedMDT																				ProtocolIE-ID ::= 422
id-SNPN-TAIBasedMDT																					ProtocolIE-ID ::= 423
id-SNPN-BasedMDT																					ProtocolIE-ID ::= 424
id-S-CPAC-Request																					ProtocolIE-ID ::= 425
id-S-CPAC-Request-Info																				ProtocolIE-ID ::= 426
id-S-CPAC-ReferenceConfigRequest																	ProtocolIE-ID ::= 427
id-S-CPAC-InterSN-ExecutionNotify																	ProtocolIE-ID ::= 428
id-S-CPAC-dataforwardinginfofromSource																ProtocolIE-ID ::= 429
id-CPACcandidatePSCells-wotherInfo-list																ProtocolIE-ID ::= 430
id-eRedcap-Bcast-Information																		ProtocolIE-ID ::= 431
id-NRPagingLongeDRXInformationforRRCINACTIVE														ProtocolIE-ID ::= 432
id-MBS-AssistanceInformation																		ProtocolIE-ID ::= 433
id-QMCCoordinationRequest																			ProtocolIE-ID ::= 434
id-QMCCoordinationResponse																			ProtocolIE-ID ::= 435
id-QoE-Measurement-Results																			ProtocolIE-ID ::= 436
id-MBSCommServiceType																				ProtocolIE-ID ::= 437
id-AssistanceInformationQoE-Meas																	ProtocolIE-ID ::= 438
id-ProtocolIE-ID-439-not-to-be-used																	ProtocolIE-ID ::= 439
id-QoERVQoEReportingPaths																			ProtocolIE-ID ::= 440
id-Src-SN-to-Tgt-SNQMCInfoInquiry																	ProtocolIE-ID ::= 441
id-DirectForwardingPathAvailabilityWithSourceMN														ProtocolIE-ID ::= 442
id-CHO-Maxnoof-CondReconfig																			ProtocolIE-ID ::= 443
id-accessed-PSCellID																				ProtocolIE-ID ::= 444
id-conditional-Reconfig-ToCancel-List																ProtocolIE-ID ::= 445
id-CHOinformation-AddReqAck																			ProtocolIE-ID ::= 446
id-CHO-CPAC-Info																					ProtocolIE-ID ::= 447
id-PDUSetQoSParameters																				ProtocolIE-ID ::= 448
id-N6JitterInformation																				ProtocolIE-ID ::= 449
id-ECNMarkingorCongestionInformationReportingRequest												ProtocolIE-ID ::= 450
id-PDUSetbasedHandlingIndicator																		ProtocolIE-ID ::= 451
id-TAISliceUnavailableCellList																		ProtocolIE-ID ::= 452
id-MobileIAB-AuthorizationStatus																	ProtocolIE-ID ::= 453
id-MIAB-MT-BAP-Address																				ProtocolIE-ID ::= 454
id-MobileIABCell																					ProtocolIE-ID ::= 455
id-sk-Counter																						ProtocolIE-ID ::= 456
id-Source-M-NG-RANnodeID																			ProtocolIE-ID ::= 457
id-ProtocolIE-ID458-NotToBeUsed																		ProtocolIE-ID ::= 458
id-SourceSN-to-TargetSN-QMCInfo																		ProtocolIE-ID ::= 459
id-RegistrationRequestForDataCollection																ProtocolIE-ID ::= 460
id-ReportCharacteristicsForDataCollection															ProtocolIE-ID ::= 461
id-ReportingPeriodicityForDataCollection															ProtocolIE-ID ::= 462
id-NodeAssociatedInfoResult																			ProtocolIE-ID ::= 463
id-SLPositioning-Ranging-Services-Info																ProtocolIE-ID ::= 464
id-XR-Bcast-Information					 															ProtocolIE-ID ::= 465
id-PDUSessionsListToBeReleased-UPError																ProtocolIE-ID ::= 466
id-MaximumDataBurstVolume																			ProtocolIE-ID ::= 467
id-CPAC-Preparation-Type																			ProtocolIE-ID ::= 468
id-UserPlaneFailureIndication																		ProtocolIE-ID ::= 469
id-MN-only-MDT-collection																			ProtocolIE-ID ::= 470
id-BarringExemptionforEmerCallInfo																	ProtocolIE-ID ::= 471
id-Transmission-Bandwidth-asymmetric																ProtocolIE-ID ::= 472
id-SRSPositioningConfigOrActivationRequest															ProtocolIE-ID ::= 473
id-NRPPaPositioningInformation																		ProtocolIE-ID ::= 474


END
